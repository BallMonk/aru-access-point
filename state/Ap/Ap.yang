module Ap {
  yang-version "1";
  
  namespace "aru-access-point/state/Ap";
  
  prefix "Ap";
  
  organization 
    "";
  
  contact
    "";
    
  description
    "access point moduel is a description with many submodules in logic,
    we try to divese it into many modules.
    In module ap we just define the base information of access point,
    like system information and state";
    
  grouping access-point-top {
    description 
      "Top level of the hierarchy and the root of tree.";
      
    list system {
      leaf ap_mac {
        type ;
      }
      
      leaf serial_number {
        type string;
      }
      
    };
    
    
  
  }
  
}
